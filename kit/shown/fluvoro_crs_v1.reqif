# Fluvoro - Customer Requirements Specification (CRS) v1

## FLV-STK-001: Keep the outlet free
The device shall prevent the gutter outlet from becoming blocked by leaves, conifer needles and small twigs during rainfall.
- ChapterName: 1 Function
- Variant: V1 and V2
- Verification: test
- Rationale: The product's purpose.

## FLV-STK-002: Automatic operation
The device shall detect a clog condition and clear it without any action by a person.
- ChapterName: 1 Function
- Variant: V1 and V2
- Verification: test
- Rationale: Removing the ladder visit is the value proposition.

## FLV-STK-003: Shredded particle size
The device shall reduce reference debris to particles whose largest dimension does not exceed 15 mm for at least 95 % of the shredded mass.
- ChapterName: 1 Function
- Variant: V1 and V2
- Verification: test
- Rationale: Particles must pass the downpipe bends and a DN 87 downpipe without building a new blockage further down.

## FLV-STK-004: Shredding throughput
The device shall shred reference debris at a rate of at least 60 g wet mass per minute while running.
- ChapterName: 1 Function
- Variant: V1 and V2
- Verification: test
- Rationale: A heavy autumn day can bring several hundred grams of wet leaves to one outlet; the device must keep up within a few short cycles.

## FLV-STK-005: Restore flow after a clog
After a clog condition is detected, the device shall restore the outlet's free discharge within 120 s in at least 95 % of clog events caused by reference debris.
- ChapterName: 1 Function
- Variant: V1 and V2
- Verification: test
- Rationale: Bounds how long water can back up and overflow during heavy rain.

## FLV-STK-006: Clog detection level
The device shall treat water standing in the outlet neck at or above a level of 30 mm above the rotor plane as a potential clog.
- ChapterName: 1 Function
- Variant: V1 and V2
- Verification: test
- Rationale: Water that rises into the funnel means the outlet cannot pass the inflow; 30 mm leaves margin before the gutter overflows.

## FLV-STK-007: Distinguish clog from heavy rain
The device shall start a shred cycle only when the clog level of FLV-STK-006 persists for at least 10 s or rises continuously over that period, so that short surges from heavy rain alone do not start the rotor.
- ChapterName: 1 Function
- Variant: V1 and V2
- Verification: test
- Rationale: Unneeded cycles waste energy, add wear and noise.

## FLV-STK-008: Start latency
The device shall start shredding within 30 s after a clog condition has been established.
- ChapterName: 1 Function
- Variant: V1 and V2
- Verification: test
- Rationale: Together with FLV-STK-005 this bounds the time water backs up.

## FLV-STK-009: Unneeded cycles
Over a reference autumn season (FLV-STK-030), no more than 10 % of shred cycles shall be started without debris being present.
- ChapterName: 1 Function
- Variant: V1 and V2
- Verification: analysis
- Rationale: Keeps the energy budget and wear within limits.

## FLV-STK-010: Verify the result of a cycle
After each shred cycle the device shall check whether the water level has fallen below the clog level and shall start a further cycle or report a persistent clog if it has not.
- ChapterName: 1 Function
- Variant: V1 and V2
- Verification: test
- Rationale: The device must not assume success; a remaining clog needs a person.

## FLV-STK-011: Persistent clog
If the clog condition persists after 3 consecutive shred cycles, the device shall stop shredding for that event and signal "service needed" (FLV-STK-061).
- ChapterName: 1 Function
- Variant: V1 and V2
- Verification: test
- Rationale: Avoids draining the battery on a clog the device cannot clear.

## FLV-STK-012: Non-shreddable objects
When a non-shreddable object (for example a stone, a ball, a plastic bag) blocks the rotor, the device shall stop the rotor, make at most 3 attempts to clear it by reversing, and then signal "service needed" without damage to the device.
- ChapterName: 1 Function
- Variant: V1 and V2
- Verification: test
- Rationale: Gutters collect more than leaves; the device must protect itself and say so.

## FLV-STK-013: Operation at night and in rain
The device shall perform all its functions independently of daylight.
- ChapterName: 1 Function
- Variant: V1 and V2
- Verification: test
- Rationale: Clogs happen during rain, often at night and with no sun.

## FLV-STK-014: Dry running
The device shall not run the rotor for longer than 5 s when the level sensor indicates no water and no clog condition, except during the self-test of FLV-STK-016.
- ChapterName: 1 Function
- Variant: V1 and V2
- Verification: test
- Rationale: Dry running adds wear and noise without benefit.

## FLV-STK-015: Motor speed and torque control
The device shall control rotor speed and torque so that it can soft-start, limit torque, detect a jam from motor current and speed, and reverse direction.
- ChapterName: 1 Function
- Variant: V1 and V2
- Verification: test
- Rationale: The motor is PWM-driven; controlled torque protects the drive, the rotor and the user.

## FLV-STK-016: Self-test
The device shall test its level sensor, motor drive and battery at least once every 24 h, run the rotor for no longer than 2 s during that test, and signal "fault" when a test fails.
- ChapterName: 1 Function
- Variant: V1 and V2
- Verification: test
- Rationale: A failed sensor must be found before the next storm, not during it.

## FLV-STK-017: Quiet hours
Between 22:00 and 06:00 local time the device shall start a shred cycle only when the water level reaches 50 mm above the rotor plane.
- ChapterName: 1 Function
- Variant: V1 and V2
- Verification: test
- Rationale: Neighbours; at night only a near-overflow justifies the noise.

## FLV-STK-018: Local time without a network
The device shall keep local time with an error of no more than 10 min per month without any network connection, and shall keep it through a battery replacement.
- ChapterName: 1 Function
- Variant: V1 and V2
- Verification: test
- Rationale: Needed by FLV-STK-017 on devices without the BLE option.

## FLV-STK-020: Discharge with the rotor stopped
With the device installed, a clean grate and the rotor stopped, the outlet shall discharge at least 80 % of the flow the same outlet discharges without the device, measured at the same water head.
- ChapterName: 2 Hydraulics
- Variant: V1 and V2
- Verification: test
- Rationale: The device must not create the overflow it is meant to prevent.

## FLV-STK-021: Fail-open drainage
With the grate and rotor completely blocked, or with the device unpowered, the device shall still drain at least 50 % of the flow of the same outlet without the device, through an overflow path that cannot be closed by debris retained by the grate.
- ChapterName: 2 Hydraulics
- Variant: V1 and V2
- Verification: test
- Rationale: No failure of the device may turn a partly blocked outlet into a fully blocked one; water on the façade is a hazard to the building.

## FLV-STK-022: Design rainfall
The device shall meet FLV-STK-020 and FLV-STK-021 for the design rainfall intensity of EN 12056-3 for the connected roof area of an NW 333 gutter outlet.
- ChapterName: 2 Hydraulics
- Variant: V1 and V2
- Verification: analysis
- Rationale: Ties the hydraulic requirements to the standard used to size roof drainage.

## FLV-STK-030: Reference autumn season
The device shall operate for a reference autumn season of 1 September to 31 December at the reference site without external charging, performing up to 4 shred cycles per day on up to 20 days and up to 1 shred cycle per day on the other days.
- ChapterName: 3 Energy
- Variant: V1 and V2
- Verification: analysis
- Rationale: The autumn leaf season is when the product must work; external charging defeats its purpose.

## FLV-STK-031: Autonomy without sun
Starting from a fully charged battery, the device shall perform at least 30 shred cycles spread over 14 days with no solar input, and keep its monitoring functions running for those 14 days.
- ChapterName: 3 Energy
- Variant: V1 and V2
- Verification: test
- Rationale: Two weeks of dark, wet weather in November is normal in Central Europe.

## FLV-STK-032: Shading and soiling
The device shall meet FLV-STK-030 with 50 % of the solar cell area shaded or covered by debris on every day of the season.
- ChapterName: 3 Energy
- Variant: V1 and V2
- Verification: analysis
- Rationale: The cap sits inside a gutter, under trees, where leaves land on it.

## FLV-STK-033: Energy reserve
The device shall keep an energy reserve sufficient for at least 5 shred cycles; when only the reserve remains it shall stop non-essential functions, keep clog clearing available, and signal "low battery".
- ChapterName: 3 Energy
- Variant: V1 and V2
- Verification: test
- Rationale: Clearing clogs is the last function the device should give up.

## FLV-STK-034: Solar charging
The device shall charge its battery from solar cells integrated in the device and shall need no mains connection and no separate panel.
- ChapterName: 3 Energy
- Variant: V1 and V2
- Verification: inspection
- Rationale: No cables on the roof; installation by a homeowner (V1).

## FLV-STK-035: Recovery from full discharge
After its battery has been fully discharged, the device shall resume normal operation automatically once solar charging has restored sufficient energy, without passing through an unsafe state and without user action.
- ChapterName: 3 Energy
- Variant: V1 and V2
- Verification: test
- Rationale: A device left dark for weeks must come back by itself.

## FLV-STK-036: Battery protection
The device shall protect its battery against over-voltage, under-voltage, over-current, short circuit and operation outside the battery manufacturer's temperature limits for charging and for discharging.
- ChapterName: 3 Energy
- Variant: V1 and V2
- Verification: test
- Rationale: Battery safety; a damaged lithium battery on a house is a fire hazard.

## FLV-STK-037: No charging below freezing
The device shall not charge its battery at a cell temperature below 0 °C or above the manufacturer's charging limit.
- ChapterName: 3 Energy
- Variant: V1 and V2
- Verification: test
- Rationale: Charging lithium cells below 0 °C causes lithium plating and lasting damage.

## FLV-STK-038: Battery chemistry
The device shall use a battery chemistry and construction whose thermal stability is at least that of lithium iron phosphate (LiFePO4).
- ChapterName: 3 Energy
- Variant: V1 and V2
- Verification: inspection
- Rationale: Mounted on a roof edge, unattended, often above wooden structures.

## FLV-STK-039: Battery life
The battery shall keep at least 70 % of its rated capacity after 5 years of use at the reference site.
- ChapterName: 3 Energy
- Variant: V1 and V2
- Verification: analysis
- Rationale: Matches the replacement interval a homeowner accepts.

## FLV-STK-040: Battery replaceable by the user
The battery shall be removable and replaceable by the end user with no tools, or with commercially available tools only, and without damage to the device or the battery.
- ChapterName: 3 Energy
- Variant: V1 and V2
- Verification: demonstration
- Rationale: Battery Regulation (EU) 2023/1542, Article 11 (portable batteries in appliances).

## FLV-STK-041: Standby consumption
The device's average power consumption while monitoring with no shred cycle shall not exceed 2 mW.
- ChapterName: 3 Energy
- Variant: V1 and V2
- Verification: test
- Rationale: Standby dominates the energy budget on most days of the year.

## FLV-STK-042: State of charge reporting
The device shall estimate its battery state of charge with an error of no more than 10 percentage points and report it through its interfaces (FLV-STK-061, FLV-STK-067).
- ChapterName: 3 Energy
- Variant: V1 and V2
- Verification: test
- Rationale: Needed for the reserve logic and to warn the user before the battery is empty.

## FLV-STK-043: Off-season storage
The device shall survive 8 months installed without debris, with only solar charging, without damage to the battery from deep discharge or over-charge.
- ChapterName: 3 Energy
- Variant: V1 and V2
- Verification: test
- Rationale: Spring and summer are mostly idle; the battery must not die from neglect.

## FLV-STK-050: Operating temperature
The device shall operate at ambient temperatures from -20 °C to +50 °C, and shall withstand -30 °C to +80 °C without operating (surface temperature of a dark cap in summer sun).
- ChapterName: 4 Environment
- Variant: V1 and V2
- Verification: test
- Rationale: Roof-edge climate in Central Europe, including sun-heated surfaces.

## FLV-STK-051: Ice and frost
The device shall not be damaged by water freezing inside it, shall not run the rotor while the rotor is held by ice, and shall resume normal operation after thawing without user action.
- ChapterName: 4 Environment
- Variant: V1 and V2
- Verification: test
- Rationale: Water stands in outlets in winter; trying to shred ice damages the drive and drains the battery.

## FLV-STK-052: Ingress protection of the electronics
The compartment holding electronics, battery and motor shall meet IP67 to IEC 60529.
- ChapterName: 4 Environment
- Variant: V1 and V2
- Verification: test
- Rationale: The compartment can be submerged briefly when the gutter overflows.

## FLV-STK-053: UV resistance
All external plastic parts shall keep their function and at least 80 % of their tensile strength after artificial weathering equivalent to 10 years of outdoor exposure in Central Europe.
- ChapterName: 4 Environment
- Variant: V1 and V2
- Verification: test
- Rationale: Permanent sun exposure on the roof edge.

## FLV-STK-054: Gutter materials
The device shall cause no galvanic or chemical corrosion of titanium zinc, copper, aluminium or coated steel gutters and outlets it is in contact with, and shall not itself corrode in contact with them.
- ChapterName: 4 Environment
- Variant: V1 and V2
- Verification: analysis
- Rationale: Metal gutters fail quickly at contact points with incompatible metals; copper run-off attacks zinc and aluminium.

## FLV-STK-055: Hail and impact
The solar cap shall withstand mechanical impact of IK08 to IEC 62262 without loss of function or watertightness.
- ChapterName: 4 Environment
- Variant: V1 and V2
- Verification: test
- Rationale: Hail and falling branches.

## FLV-STK-056: Snow and walking load
The device shall withstand a static load of 300 N on the cap without damage.
- ChapterName: 4 Environment
- Variant: V1 and V2
- Verification: test
- Rationale: Snow load and a person leaning on the gutter during other roof work.

## FLV-STK-057: Service life
The device, excluding battery and wear parts, shall have a service life of at least 10 years at the reference site.
- ChapterName: 4 Environment
- Variant: V1 and V2
- Verification: analysis
- Rationale: Expected life of a roof drainage accessory.

## FLV-STK-060: Status visible from the ground
The device shall show its state (normal, low battery, service needed, fault, maintenance mode) by a light signal that a person can recognise in daylight from the ground at a distance of 6 m.
- ChapterName: 5 User interaction
- Variant: V1 and V2
- Verification: test
- Rationale: The user must be able to check the device without a ladder.

## FLV-STK-061: Service needed
The device shall signal "service needed" for a persistent clog, a non-shreddable object, worn cutting parts or a failed self-test, and keep signalling until the cause is removed.
- ChapterName: 5 User interaction
- Variant: V1 and V2
- Verification: test
- Rationale: The device must say when it needs a person.

## FLV-STK-062: Signalling energy
The light signal of FLV-STK-060 shall not use more than 10 % of the standby energy budget of FLV-STK-041.
- ChapterName: 5 User interaction
- Variant: V1 and V2
- Verification: analysis
- Rationale: Signalling must not drain the battery it reports on.

## FLV-STK-063: Noise during shredding
The A-weighted sound pressure level during shredding shall not exceed 65 dB(A) at 1 m from the device.
- ChapterName: 5 User interaction
- Variant: V1 and V2
- Verification: test
- Rationale: Residential area; the device is near windows.

## FLV-STK-064: No noise at rest
The device shall produce no audible sound while monitoring.
- ChapterName: 5 User interaction
- Variant: V1 and V2
- Verification: test
- Rationale: Residential area.

## FLV-STK-065: Event log
The device shall record at least the last 200 events (shred cycles with start, duration and result, jams, faults, low battery, maintenance mode) with their local time, and keep them through a battery replacement.
- ChapterName: 5 User interaction
- Variant: V1 and V2
- Verification: test
- Rationale: Service diagnosis and evidence of operation.

## FLV-STK-066: Service access to the log
A service technician shall be able to read the event log, the hardware and software versions and the serial number on site without opening the sealed compartment.
- ChapterName: 5 User interaction
- Variant: V1 and V2
- Verification: demonstration
- Rationale: Diagnosis without breaking the IP67 seal.

## FLV-STK-067: Smartphone app (option)
With the connectivity option, the device shall provide its state, state of charge, event log and notifications of "service needed" and "fault" to a smartphone app over Bluetooth Low Energy.
- ChapterName: 5 User interaction
- Variant: Connectivity option (V1 and V2)
- Verification: demonstration
- Rationale: Convenience for users who want notifications.

## FLV-STK-070: Functional safety frame
The supplier shall develop the device in accordance with ISO 26262:2018 Parts 2 to 9, tailored to the item, including an item definition, a hazard analysis and risk assessment that determines the ASIL of each safety goal, a functional and a technical safety concept, and a safety case.
- ChapterName: 6 Safety
- Variant: V1 and V2
- Verification: inspection
- Rationale: Contractual development frame required by the customer. ASILs are to be determined by the supplier, not given here.

## FLV-STK-071: Protection of a person's hand
The rotor shall not start or run while the cap is removed, while the device is in maintenance mode, or in any other situation in which a person's hand can reach the rotor.
- ChapterName: 6 Safety
- Variant: V1 and V2
- Verification: test
- Rationale: Gutter cleaning by hand is the most likely contact with the device.

## FLV-STK-072: Inaccessible rotating parts
When the device is installed and closed, the rotating parts shall not be reachable by the upper limb, using the safety distances of EN ISO 13857.
- ChapterName: 6 Safety
- Variant: V1 and V2
- Verification: inspection
- Rationale: Machinery safety for rotating cutting parts.

## FLV-STK-073: Maintenance mode
A person shall be able to put the device into a maintenance mode that disables the rotor, by a means operable without tools at the device, and the device shall confirm the mode by its light signal before the person reaches into it.
- ChapterName: 6 Safety
- Variant: V1 and V2
- Verification: demonstration
- Rationale: Safe cleaning of the grate and removal of objects.

## FLV-STK-074: No unintended start after a fault
After a fault that stopped the rotor for safety reasons, the rotor shall not start again until the fault has been cleared and the device has passed its self-test.
- ChapterName: 6 Safety
- Variant: V1 and V2
- Verification: test
- Rationale: An unexpected restart is the most dangerous moment for a person removing a blockage.

## FLV-STK-075: Limited force at the rotor
The force and energy the rotor can exert shall be limited such that contact with the rotating parts while the device runs causes no more than a minor, reversible injury to a finger.
- ChapterName: 6 Safety
- Variant: V1 and V2
- Verification: test
- Rationale: Defence in depth behind FLV-STK-071 and FLV-STK-072; relies on controlled torque (FLV-STK-015).

## FLV-STK-076: No fire on the building
No single fault of the device, including a battery cell fault, shall cause flames or molten material to leave the device enclosure.
- ChapterName: 6 Safety
- Variant: V1 and V2
- Verification: test
- Rationale: The device sits on a roof edge, often above timber.

## FLV-STK-077: Enclosure flammability
Plastic parts enclosing the battery and electronics shall be rated V-0 to UL 94 / IEC 60695-11-10 at the wall thickness used.
- ChapterName: 6 Safety
- Variant: V1 and V2
- Verification: inspection
- Rationale: Containment of an internal fire.

## FLV-STK-078: Safety extra-low voltage
All accessible circuits shall be safety extra-low voltage, with no voltage above 60 V DC anywhere in the device.
- ChapterName: 6 Safety
- Variant: V1 and V2
- Verification: inspection
- Rationale: Electrical safety for a device handled by homeowners on a ladder.

## FLV-STK-079: No overflow caused by the device
No failure of the device shall reduce the outlet's discharge below the fail-open drainage of FLV-STK-021.
- ChapterName: 6 Safety
- Variant: V1 and V2
- Verification: analysis
- Rationale: Water overflowing onto the façade damages the building and freezes on walkways.

## FLV-STK-080: Safe state
On detecting a fault that affects safe operation, the device shall stop the rotor and keep it stopped, keep the fail-open drainage of FLV-STK-021, and signal "fault".
- ChapterName: 6 Safety
- Variant: V1 and V2
- Verification: test
- Rationale: Stopping the rotor is safe for people; drainage remains through the overflow path.

## FLV-STK-090: CE marking
The device shall comply with, and be CE marked under, the Machinery Regulation (EU) 2023/1230, the EMC Directive 2014/30/EU and the RoHS Directive 2011/65/EU.
- ChapterName: 7 Compliance
- Variant: V1 and V2
- Verification: inspection
- Rationale: Legal market access in the EU.

## FLV-STK-091: Machinery risk assessment
The supplier shall perform and document a risk assessment and risk reduction to EN ISO 12100.
- ChapterName: 7 Compliance
- Variant: V1 and V2
- Verification: inspection
- Rationale: Required for the Machinery Regulation conformity assessment; separate from the ISO 26262 HARA.

## FLV-STK-092: Control software safety class
Software that performs a protective function shall meet the requirements for Class B control functions of IEC 60730-1 Annex H, in addition to FLV-STK-070.
- ChapterName: 7 Compliance
- Variant: V1 and V2
- Verification: inspection
- Rationale: Product-compliance view of the protective software functions; kept apart from the functional-safety lifecycle.

## FLV-STK-093: Electromagnetic compatibility
The device shall meet emission limits of CISPR 14-1 and immunity requirements of CISPR 14-2.
- ChapterName: 7 Compliance
- Variant: V1 and V2
- Verification: test
- Rationale: Household appliance EMC standards for a motor-driven device.

## FLV-STK-094: Battery Regulation
The device and its battery shall comply with the Battery Regulation (EU) 2023/1542, including labelling, information and take-back obligations.
- ChapterName: 7 Compliance
- Variant: V1 and V2
- Verification: inspection
- Rationale: Legal market access for products containing batteries.

## FLV-STK-095: WEEE
The device shall comply with the WEEE Directive 2012/19/EU, including the crossed-out wheelie bin marking.
- ChapterName: 7 Compliance
- Variant: V1 and V2
- Verification: inspection
- Rationale: End-of-life obligations.

## FLV-STK-096: General product safety
The device shall comply with the General Product Safety Regulation (EU) 2023/988, including traceability information on the product.
- ChapterName: 7 Compliance
- Variant: V1 and V2
- Verification: inspection
- Rationale: Applies to consumer products placed on the EU market.

## FLV-STK-097: Radio equipment (option)
With the connectivity option, the device shall comply with the Radio Equipment Directive 2014/53/EU, including the cybersecurity requirements of Delegated Regulation (EU) 2022/30 as given in EN 18031-1, and with the Cyber Resilience Act (EU) 2024/2847 from its date of application.
- ChapterName: 7 Compliance
- Variant: Connectivity option (V1 and V2)
- Verification: inspection
- Rationale: A radio interface brings radio and cybersecurity law.

## FLV-STK-098: Material marking
Plastic parts heavier than 10 g shall be marked with their material to ISO 11469.
- ChapterName: 7 Compliance
- Variant: V1 and V2
- Verification: inspection
- Rationale: Recycling at end of life.

## FLV-STK-100: Cybersecurity engineering (option)
With the connectivity option, the supplier shall perform cybersecurity engineering to ISO/SAE 21434, including a threat analysis and risk assessment of the radio interface and the firmware update path.
- ChapterName: 8 Cybersecurity (connectivity option)
- Variant: Connectivity option (V1 and V2)
- Verification: inspection
- Rationale: The radio interface is the only remote attack surface; a malicious command could start the rotor.

## FLV-STK-101: No remote rotor start (option)
No command received over the radio interface shall be able to start the rotor or override a safety function.
- ChapterName: 8 Cybersecurity (connectivity option)
- Variant: Connectivity option (V1 and V2)
- Verification: test
- Rationale: Keeps every safety function local; the app may observe, not actuate.

## FLV-STK-102: Authenticated firmware (option)
With the connectivity option, the device shall accept only firmware that is cryptographically signed by the manufacturer, and shall keep running its previous firmware if an update fails.
- ChapterName: 8 Cybersecurity (connectivity option)
- Variant: Connectivity option (V1 and V2)
- Verification: test
- Rationale: EN 18031-1 and the Cyber Resilience Act; a failed update must not brick the device in the middle of a season.

## FLV-STK-103: Pairing (option)
Pairing with a smartphone shall require physical presence at the device.
- ChapterName: 8 Cybersecurity (connectivity option)
- Variant: Connectivity option (V1 and V2)
- Verification: demonstration
- Rationale: Prevents a neighbour's or passer-by's phone from taking over the device.

## FLV-STK-110: V1 fit
The V1 insert shall fit gutter outlets for NW 333 gutters with DN 87 and DN 100 downpipes made to EN 612.
- ChapterName: 9 Mechanics
- Variant: V1 insert
- Verification: test
- Rationale: Most common residential size in Germany; other sizes are a later variant.

## FLV-STK-111: V1 installation without tools
One person on a ladder shall be able to install or remove the V1 insert without tools within 5 min.
- ChapterName: 10 Installation
- Variant: V1 insert
- Verification: demonstration
- Rationale: Retrofit by the homeowner.

## FLV-STK-112: V1 no change to the gutter
Installing the V1 insert shall require no modification of the gutter, the outlet or the downpipe, and removing it shall leave them in their original state.
- ChapterName: 10 Installation
- Variant: V1 insert
- Verification: inspection
- Rationale: Retrofit, reversible.

## FLV-STK-113: V1 height
No part of the installed V1 insert shall rise above the gutter's front rim.
- ChapterName: 9 Mechanics
- Variant: V1 insert
- Verification: inspection
- Rationale: A part above the rim would deflect water over the edge and be visible from the street.

## FLV-STK-114: V1 clips and bead free
The V1 insert shall not rest on or load the outlet's clips or the gutter bead.
- ChapterName: 9 Mechanics
- Variant: V1 insert
- Verification: inspection
- Rationale: Loaded clips loosen and the outlet starts to leak.

## FLV-STK-115: V1 retention
The installed V1 insert shall stay in place at the maximum design flow, when ice forms around it, and under a lifting force of 50 N.
- ChapterName: 9 Mechanics
- Variant: V1 insert
- Verification: test
- Rationale: It must not float, be pushed out by ice or lifted by wind.

## FLV-STK-116: V1 mass
The V1 insert shall not weigh more than 1.2 kg including the battery.
- ChapterName: 9 Mechanics
- Variant: V1 insert
- Verification: inspection
- Rationale: Handling on a ladder; load on the gutter brackets.

## FLV-STK-117: V1 structure-borne noise
Shredding shall not transmit vibration to the gutter that causes audible rattling of the gutter or the downpipe brackets.
- ChapterName: 9 Mechanics
- Variant: V1 insert
- Verification: test
- Rationale: Metal gutters act as resonators.

## FLV-STK-120: V2 fit
The V2 replacement outlet shall replace an EN 612 outlet for NW 333 gutters, with variants for DN 87 and DN 100 downpipes.
- ChapterName: 9 Mechanics
- Variant: V2 replacement outlet
- Verification: inspection
- Rationale: Same first size as V1.

## FLV-STK-121: V2 materials
The V2 replacement outlet shall be available in titanium zinc, copper and aluminium, matching the gutter material.
- ChapterName: 9 Mechanics
- Variant: V2 replacement outlet
- Verification: inspection
- Rationale: Roofers do not mix gutter metals (see FLV-STK-054).

## FLV-STK-122: V2 installation by a roofer
A roofer shall be able to install the V2 replacement outlet with the joining methods used for standard outlets of the same material (soldering, riveting with sealant, or clip), within 20 min.
- ChapterName: 10 Installation
- Variant: V2 replacement outlet
- Verification: demonstration
- Rationale: No new skills or tools for the trade.

## FLV-STK-123: V2 service without removal
The cap, the battery and the cutting parts of V2 shall be removable for service without removing the outlet from the gutter.
- ChapterName: 10 Installation
- Variant: V2 replacement outlet
- Verification: demonstration
- Rationale: The outlet is a fixed part of the roof drainage.

## FLV-STK-124: V2 mass
The V2 replacement outlet shall not weigh more than 2.0 kg including the battery.
- ChapterName: 9 Mechanics
- Variant: V2 replacement outlet
- Verification: inspection
- Rationale: Load on the gutter at the outlet.

## FLV-STK-130: Maintenance
Apart from replacing the battery and wear parts and cleaning the grate, the device shall need no maintenance during its service life.
- ChapterName: 11 Lifecycle
- Variant: V1 and V2
- Verification: analysis
- Rationale: The product exists to reduce maintenance.

## FLV-STK-131: Wear parts
The cutting parts shall last at least 5 autumn seasons at the reference load of FLV-STK-030 and shall be replaceable by the end user without tools.
- ChapterName: 11 Lifecycle
- Variant: V1 and V2
- Verification: test
- Rationale: Cutting edges wear; the rest of the device should not be scrapped for it.

## FLV-STK-132: Worn cutting parts
The device shall detect when its cutting performance has fallen below the throughput of FLV-STK-004 and signal "service needed".
- ChapterName: 11 Lifecycle
- Variant: V1 and V2
- Verification: test
- Rationale: The user cannot see the blades.

## FLV-STK-133: Firmware update
The device firmware shall be updatable in the field by a service technician without opening the sealed compartment.
- ChapterName: 11 Lifecycle
- Variant: V1 and V2
- Verification: demonstration
- Rationale: Field fixes without replacing devices.

## FLV-STK-134: Spare parts
Battery, cap and cutting parts shall be available as spare parts for at least 7 years after the last unit of a variant is placed on the market.
- ChapterName: 11 Lifecycle
- Variant: V1 and V2
- Verification: inspection
- Rationale: Repairability; customer expectation for a 10-year product.

## FLV-STK-135: Identification
Each device shall carry a unique serial number readable on the device and through the service interface, and shall report its hardware and software versions.
- ChapterName: 11 Lifecycle
- Variant: V1 and V2
- Verification: inspection
- Rationale: Traceability (GPSR) and field service.

## FLV-STK-140: Process capability
The supplier shall perform the system and software engineering processes to Automotive SPICE 4.0 capability level 2 for SYS.1 to SYS.5, SWE.1 to SWE.6, MAN.3, SUP.1, SUP.8, SUP.9 and SUP.10.
- ChapterName: 13 Project
- Variant: V1 and V2
- Verification: inspection
- Rationale: Customer's process frame.

## FLV-STK-141: Bidirectional traceability
The supplier shall maintain bidirectional traceability from each stakeholder requirement to system requirements, software requirements, architecture elements, code and test cases.
- ChapterName: 13 Project
- Variant: V1 and V2
- Verification: inspection
- Rationale: Required by ASPICE and ISO 26262; makes change impact analysable.

## FLV-STK-142: Deliverables
The supplier shall deliver the system and software requirements, the system and software architecture, the safety work products of FLV-STK-070, the source code, the test specifications and test reports, and the traceability report.
- ChapterName: 13 Project
- Variant: V1 and V2
- Verification: inspection
- Rationale: Defines what the customer receives.

## FLV-STK-143: Change management
The supplier shall assess the impact of every change to these requirements on all affected work products before implementing it, and shall record the assessment.
- ChapterName: 13 Project
- Variant: V1 and V2
- Verification: inspection
- Rationale: SUP.10; changes during development are expected.

## FLV-STK-144: Product cost
The bill of materials and assembly cost at 50 000 units per year shall not exceed EUR 45 for V1 and EUR 70 for V2, excluding the connectivity option.
- ChapterName: 13 Project
- Variant: V1 and V2
- Verification: analysis
- Rationale: Consumer price point for a gutter accessory; to be confirmed by a market check.

## FLV-STK-145: End-of-line test
Every produced device shall pass an end-of-line test of level sensing, motor drive and rotor direction, battery management and light signal before shipping.
- ChapterName: 12 Quality
- Variant: V1 and V2
- Verification: inspection
- Rationale: Production quality; supports the safety case.

## FLV-STK-146: User documentation
The device shall be supplied with installation, operating, safety and battery-replacement instructions in the official languages of the EU member states where it is sold.
- ChapterName: 7 Compliance
- Variant: V1 and V2
- Verification: inspection
- Rationale: Machinery Regulation and GPSR information obligations.
